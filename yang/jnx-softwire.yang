module jnx-softwire {
  namespace "http://yang.juniper.net/software/aug";
  prefix "jnx-swire";

  import ietf-inet-types {prefix inet; }
  import ietf-softwire {prefix sw; }

  organization "Juniper Networks, Inc.";

  revision 2016-07-19 {
    description
      "Juniper software augments. ";
  }

  augment "/sw:softwire-config/sw:binding/sw:br" {
    leaf binding-table-file {
      type string;
      description "Complete path of the binding table file";
    }
  }

  augment "/sw:softwire-config/sw:binding/sw:br/sw:br-instances/sw:br-instance" {
    leaf ipv6_address {
      type inet:ipv6-address;
    }
    leaf ipv4_address {
      type inet:ipv4-address;
    }
    leaf ipv6_vlan {
      type uint16 {
        range 0..4094;
      }
    }
    leaf ipv4_vlan {
      type uint16 {
        range 0..4094;
      }
    }
    leaf hairpinning {
      type boolean;
      default false;
    }
    leaf fragmentation {
      type boolean;
      default false;
    }
    leaf cache_refresh_interval {
      type uint32;
      units seconds;
      default 1;
    }
    leaf icmpv6_rate_limiter_n_packets {
      type uint32;
    }
    leaf icmpv6_rate_limiter_n_seconds {
      type uint32;
      default 1;
    }
    leaf policy_icmpv6_incoming {
      type enumeration {
        enum allow;
        enum drop;
      }
    }
    leaf policy_icmpv6_outgoing {
      type enumeration {
        enum allow;
        enum drop;
      }
    }
    leaf policy_icmpv4_incoming {
      type enumeration {
        enum allow;
        enum drop;
      }
    }
    leaf policy_icmpv4_outgoing {
      type enumeration {
        enum allow;
        enum drop;
      }
    }
    leaf ipv6_ingress_filter {
      type string;
      description
        "IPv6 ingress filter in libpcap format";
    }
    leaf ipv6_egress_filter {
      type string;
      description
        "IPv6 egress filter in libpcap format";
    }
    leaf ipv4_ingress_filter {
        type string;
        description
          "IPv4 ingress filter in libpcap format";
    }
    leaf ipv4_egress_filter {
      type string;
      description
        "IPv4 egress filter in libpcap format";
    }
    leaf ingress_drop_action {
      type enumeration {
        enum flush;
        enum warn;
      }
      default flush;
      description 
        "jit.flush() gets triggered if set to flush, otherwise just a warning message is created.
         default is flush";
    }
    leaf ingress_drop_threshold {
      type uint32;
      default 100000;
      description
        "Number of ingress discard packets per drop interval must be exceeded before trigger jit.flush()";
    }
    leaf ingress_drop_interval {
      type uint32;
      default 1000000;
      description
        "drop interval in msec";
    }
    leaf ingress_drop_wait {
      type uint32;
      default 20;
      description
        "grace period between jit.flush() in seconds";
    }
  }
}

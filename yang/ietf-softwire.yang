module ietf-softwire {
  namespace "urn:ietf:params:xml:ns:yang:ietf-softwire";
  prefix "softwire";

  import ietf-inet-types {prefix inet; }

  organization "Softwire Working Group";

  contact
    "
    Qi Sun sunqi.ietf@gmail.com
    Hao Wang wangh13@mails.tsinghua.edu.cn
    Yong Cui yong@csnet1.cs.tsinghua.edu.cn
    Ian Farrer ian.farrer@telekom.de
    Mohamed Boucadair mohamed.boucadair@orange.com
    Rajiv Asati rajiva@cisco.com
    ";

  description
    "This document defines a YANG data model for the configuration and
    management of IPv4-in-IPv6 Softwire Border Routers and Customer
    Premises Equipment. It covers Lightweight 4over6, MAP-E and MAP-T
    Softwire mechanisms.

    Copyright (c) 2014 IETF Trust and the persons identified
    as authors of the code. All rights reserved.
    This version of this YANG module is part of RFC XXX; see the RFC
    itself for full legal notices.";

  revision 2015-09-30 {
    description
      "Version-04: fix YANG syntax; Add flags to map-rule; Remove
                  the map-rule-type element. ";
       reference "tbc";
  }

  revision 2015-04-07 {
    description
      "Version-03: Integrate lw4over6; Updata state nodes; Correct
          grammar errors; Reuse groupings; Update descriptions.
          Simplify the model.";
       reference "tbc";
  }

  revision 2015-02-10 {
    description
      "Version-02: Add notifications.";
       reference "tbc";
  }


  revision 2015-02-06 {
    description
      "Version-01: Correct grammar errors; Reuse groupings; Update
      descriptions.";
       reference "tbc";
  }

  revision 2015-02-02 {
    description
      "Initial revision.";
       reference "tbc";
  }

/*
 * Features
 */

  feature lw4over6 {
    description
    "Lightweight 4over6 (lw4over6) is an IPv4-over-IPv6 tunnelling
     transition mechanism. Lightweight 4over6 is a solution designed
     specifically for complete independence between IPv6 subnet
     prefix (and /128 IPv6 address) and IPv4 address with or
     without IPv4 address sharing.

     This is accomplished by maintaining state for
     each softwire (per-subscriber state) in the central lwAFTR and
     a hub-and-spoke forwarding architecture. In order to delegate
     the NAPT function and achieve IPv4 address sharing,
     port-restricted IPv4 addresses needs to be allocated to CEs.";

   reference
      "I-D.ietf-softwire-lw4over6";
  }

  feature lwaftr {
    if-feature lw4over6;
    description
     "The AFTRs (BRs) for Lightweight 4over6, so-called lwAFTR. This
      feature indicates that a instance functions as a lwAFTR.
      A lwAFTR is an IPv4-in-IPv6 tunnel concentrator that maintains
      per-subscriber IPv4-IPv6 address binding.";
  }

/*
 * Grouping
 */

  grouping port-set {
    description
      "Use the PSID algorithm to represent a range of transport layer
      ports.";
    leaf offset {
      type uint8 {
        range 0..16;
      }
     mandatory true;
     description
       "The number of offset bits. In Lightweight 4over6, the defaul
       value is 0 for assigning one contiguous port range. In MAP-E/T,
       the default value is 6, which excludes system ports by default
       and assigns distributed port ranges. If the this parameter is
       larger than 0, the value of offset MUST be greater than 0.";
    }
    leaf psid {
      type uint16;
      mandatory true;
      description
        "Port Set Identifier (PSID) value, which identifies a set
        of ports algorithmically.";
    }
    leaf psid-len {
      type uint8 {
        range 0..16;
      }
      mandatory true;
      description
        "The length of PSID, representing the sharing ratio for an
        IPv4 address.";
    }
  }

  grouping binding-entry {
    description
      "The lwAFTR maintains an address binding table that contains
      thebinding between the lwB4's IPv6 address, the allocated IPv4
      address and restricted port-set.";
    leaf binding-ipv6info {
      type union {
        type inet:ipv6-address;
        type inet:ipv6-prefix;
      }
      mandatory true;
      description
        "The IPv6 information for a binding entry.
         If it's an IPv6 prefix, it indicates that
         the IPv6 source address of the lwB4 is constructed
         according to the description in RFC7596;
         if it's an IPv6 address, it means the lwB4 uses
         any /128 address from the assigned IPv6 prefix.
         ";
    }
    leaf binding-ipv4-addr {
      type inet:ipv4-address;
      mandatory true;
      description
        "The IPv4 address assigned to the lwB4, which is
         used as the IPv4 external address
         for lwB4 local NAPT44.";
    }
    container port-set {
      description
        "For Lightweight 4over6, the default value
        of offset should be 0, to configure one contiguous
        port range.";
      uses port-set {
        refine offset {
          default "0";
        }
      }
    }
    leaf lwaftr-ipv6-addr {
      type inet:ipv6-address;
          mandatory true;
      description
        "The IPv6 address for lwaftr.";
    }
    leaf lifetime {
      type uint32;
      units seconds;
      description "The lifetime for the binding entry";
    }
  }

  grouping interface-params {
    leaf mtu {
      type uint16;
      mandatory true;
    }
    container icmp-params {
      container policy {
        leaf incoming {
          type enumeration {
            enum ALLOW;
            enum DENY;
          }
        }
        leaf outgoing {
          type enumeration {
            enum ALLOW;
            enum DENY;
          }
        }
      }
      container rate-limit {
        leaf n_packets {
          type uint32;
          mandatory true;
        }
        leaf n_seconds {
          type uint32;
          default 1;
        }
      }
    }
    leaf cache_refresh_interval {
      type uint32;
      units seconds;
    }
  }

/*
 * Configuration Data Nodes
 */


  container softwire-config {
    description
      "The configuration data for Softwire instances. And the shared
      data describes the softwire data model which is common to all of
      the different softwire mechanisms, such as description.";
    leaf description {
      type string;
      description
        "A textual description of Softwire.";
    }
    container lw4over6 {
      if-feature lw4over6;
      description
        "lw4over6 configuration.";
      container lwaftr {
        if-feature lwaftr;
        description
          "Indicate this instance supports the lwAFTR function. The
          instances advertise the lwaftr feature through the
          capability exchange mechanism when a NETCONF session is
          established.";
        leaf enable {
          type boolean;
          description
            "Enable/disable the lwAFTR function.";
        }

        container lwaftr-instances {
          description
            "A set of lwAFTRs to be configured.";
          list lwaftr-instance {
            key "id";
          description
            "A set of lwAFTRs to be configured.";
            leaf id {
              type uint32;
              description "An instance identifier.";
            }
            leaf lwaftr-name {
              type string;
              description "The name for the lwaftr.";
            }
            leaf softwire-num-threshold {
              type uint32;
              mandatory true;
              description
                "The maximum number of tunnels that can be created on
                the lwAFTR.";
            }
            leaf tunnel-payload-mtu {
              type uint16;
              mandatory true;
              description
                "The payload MTU for Lightweight 4over6 tunnel.";
            }
            leaf tunnel-path-mru {
              type uint16;
              mandatory true;
              description
                "The path MRU for Lightweight 4over6 tunnel.";
            }
            container binding-table {
              description "id";
              list binding-entry {
                key "binding-ipv6info";
                description "id";
                uses binding-entry;
              }
            }
          }
        }
      }
    }
  }
}

module jnx-softwire {
  namespace "http://yang.juniper.net/software/aug";
  prefix "jnx-swire";

  import ietf-softwire {prefix sw; }

  organization "Juniper networks";

  revision 2016-07-17 {
    description
      "Juniper software augments. ";
  }


  augment "/sw:softwire-config/sw:lw4over6/sw:lwaftr" {
            leaf binding-table {
                type string;
                description "Complete path of the binding table file";
            }
  }
}

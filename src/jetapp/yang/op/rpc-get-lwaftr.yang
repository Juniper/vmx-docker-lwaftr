/*
* Copyright (c) 2016 Juniper Networks, Inc.
* All rights reserved.
*/

module rpc-get-lwaftr {
  namespace "http://yang.juniper.net/yang/1.1/jrpc";
  prefix jrpc;

  import junos-extension-odl{
    prefix junos-odl;
  }

  import junos-extension{
    prefix junos;
  }

  organization
    "Juniper Networks, Inc.";

  description
    "Junos YANG module for fetching Snabb Lwaftr statistics";

rpc get-lwaftr-state {
    description "Fetch state information of all the Snabb instances";
    junos:command "show lwaftr state" {
      junos:action-execute {
        junos:script "rpc_get_lwaftr_state.py";
      }
     }
     output {
       container instance {
           leaf id_error {
             junos-odl:template "No instance Found";
             type string;
             description "No such instance";
           }
           leaf rpc_error {
             junos-odl:template "Error connecting to snabb";
             type string;
             description "Error connecting to snabb";
           }
           leaf id {
              junos-odl:template "Instance id: %s";
              type string;
              description "ID of instance";
           }
           leaf pid {
              junos-odl:template "\tProcess ID of this instance:                      %17s";
              type string;
              description "pid of instance";
           }
           leaf next_hop_mac_v4 {
              junos-odl:template "\tNexthop v4 mac address:                           %17s";
              type string;
              description "IPv4 nexthop mac";
           }
           leaf next_hop_mac_v6 {
              junos-odl:template "\tNexthop v6 mac address:                           %17s";
              type string;
              description "IPv6 nexthop mac";
           }
	   leaf rxpackets {
	      junos-odl:template "\tReceived packets:                                 %17s";
	      type string;
              description "Recieved packets";
	   }
	   leaf txpackets {
	      junos-odl:template "\tTransmitted packets:                              %17s";
	      type string;
              description "Sent packets";
	   }
	   leaf rxdrop {
	      junos-odl:template "\tReceived packets that were dropped:               %17s";
	      type string;
              description "Recieved packet drops";
	   }
	   leaf txdrop {
	      junos-odl:template "\tSent packets that were dropped:                   %17s";
	      type string;
              description "Sent packet drops";
	   }
	   leaf breaths {
	      junos-odl:template "\tBreaths count:                                    %17s";
	      type string;
	      description "Breaths count";
	   }
           container instance-format {
             junos-odl:cli-format;
       	     junos-odl:header "Snabb State \n";

       	junos-odl:picture "
@\\n
@\\n
@\\n
@<<<<<<<<<<<<<<<<<<<<<<<<
@<<<<<<<<<<<<<<<<<<<<<<<<
@<<<<<<<<<<<<<<<<<<<<<<<<
@<<<<<<<<<<<<<<<<<<<<<<<<
@<<<<<<<<<<<<<<<<<<<<<<<<
@<<<<<<<<<<<<<<<<<<<<<<<<
@<<<<<<<<<<<<<<<<<<<<<<<<
@<<<<<<<<<<<<<<<<<<<<<<<<
";
       junos-odl:line {
           junos-odl:field "id_error";
       }
       junos-odl:line {
           junos-odl:field "rpc_error";
       }
       junos-odl:line {
           junos-odl:field "id";
       }
       junos-odl:line {
           junos-odl:field "pid";
       }
       junos-odl:line {
           junos-odl:field "next_hop_mac_v4";
       }
       junos-odl:line {
           junos-odl:field "next_hop_mac_v6";
       }
       junos-odl:line {
           junos-odl:field "rxpackets";
       }
       junos-odl:line {
           junos-odl:field "txpackets";
       }
       junos-odl:line {
           junos-odl:field "rxdrop";
       }
       junos-odl:line {
           junos-odl:field "txdrop";
       }
       junos-odl:line {
           junos-odl:field "breaths";
       }
           }
       }
     }
}

}
